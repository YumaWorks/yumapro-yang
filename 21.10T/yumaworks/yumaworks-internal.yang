module yumaworks-internal {

    namespace "http://yumaworks.com/ns/yumaworks-internal";

    prefix "yint";

    import yuma-ncx { prefix ncx; }

    organization "YumaWorks, Inc.";

    contact
        "Support <support at yumaworks.com>";

    description
       "Internal definitions used by the netconfd-pro server.

     Copyright (c) 2019, YumaWorks, Inc. All rights reserved.

     Redistribution and use in source and binary forms, with or
     without modification, is permitted pursuant to, and subject
     to the license terms contained in, the BSD 3-Clause License
     http://opensource.org/licenses/BSD-3-Clause";

    revision 2019-01-22 {
        description
          "Initial version";
    }

    rpc replay-config {
      ncx:hidden;
      ncx:abstract;
      description
        "Replay the running config for SIL components that have
         reset during operation.";
      // TBD: leaf-list input parameter to select sub-trees to reload
    }

}

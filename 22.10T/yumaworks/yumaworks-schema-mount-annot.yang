module yumaworks-schema-mount-annot {
  namespace "urn:yumaworks:params:xml:ns:yumaworks-schema-mount-annot";
  prefix sm-annot;

  import yumaworks-extensions { prefix ywx; }
  import ietf-yang-schema-mount { prefix schema; }

  revision 2021-12-08 {
    description
      "Initial version";
  }

  deviation /schema:schema-mounts/schema:namespace {
    deviate add {
      ywx:sil-aio-get2;
    }
  }

  deviation /schema:schema-mounts/schema:mount-point {
    deviate add {
      ywx:sil-aio-get2;
    }
  }
}

module yumaworks-nmda {
    yang-version 1.1;
    namespace "urn:ymaworks:params:xml:ns:yumaworks-nmda";
    prefix "ynmda";

    import ietf-netconf-nmda { prefix ncds; }

    import yumaworks-app-common { prefix ywapp; }

    organization "YumaWorks, Inc.";

    contact
        "Support <support at yumaworks.com>";

    description
       "Extensions to NETCONF NMDA operations.

     Copyright (c) 2026 YumaWorks, Inc. All rights reserved.

     Redistribution and use in source and binary forms, with or
     without modification, is permitted pursuant to, and subject
     to the license terms contained in, the BSD 3-Clause License
     http://opensource.org/licenses/BSD-3-Clause";

    revision 2026-04-29 {
        description
          "25.10-8:
             - First version
          ";
    }

    augment /ncds:get-data/ncds:input {
      uses ywapp:WithOwnersParm;
      uses ywapp:WithLastModifiedParm;
      uses ywapp:WithEtagParm;
      uses ywapp:ModuleTagParm;
    }

}

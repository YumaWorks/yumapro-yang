module yang-attributes {

    yang-version 1;
    namespace "urn:ietf:params:xml:ns:yang:1";
    prefix "y";

    import yuma-ncx { prefix ncx; }

    organization "YumaWorks, Inc.";

    contact
        "Support <support at yumaworks.com>";

    description
       "YANG language XML attribute definitions in YANG format.
        Used for internal parsing.

     Copyright (c) 2013 - 2016 YumaWorks, Inc. All rights reserved.

     Redistribution and use in source and binary forms, with or
     without modification, is permitted pursuant to, and subject
     to the license terms contained in, the BSD 3-Clause License
     http://opensource.org/licenses/BSD-3-Clause";

    revision 2016-01-06 {
       description
         "Add YANG 1.1 action rpc.";
    }

    revision 2013-02-18 {
       description
         "Initial version";
    }

    leaf insert {
      ncx:abstract;
      ncx:hidden;
      type enumeration {
        enum first;
        enum last;
        enum before;
        enum after;
      }
      default last;
      description "YANG insert attribute";
      reference "RFC 6020, sec. 7.8.6";
    }

    leaf key {
      ncx:abstract;
      ncx:hidden;
      type string;
      description "YANG key attribute";
      reference "RFC 6020, sec. 7.8.6";
    }

    leaf value {
      ncx:abstract;
      ncx:hidden;
      type string;
      description "YANG value attribute";
      reference "RFC 6020, sec. 7.7.7";
    }

    rpc action {
      ncx:hidden;
      description
        "YANG 1.1 action.  This node is specially parsed.
         It does not follow any YANG-supportable schema.

         The action container should have 1 subtree starting
         with a top-level data node.  There should be 1 subtree
         that matches an action-stmt definition.";
    }

}

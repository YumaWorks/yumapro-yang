module yumaworks-system-dev {
  namespace "http://yumaworks.com/ns/yumaworks-system-dev";
  prefix "sysdev";

  import ietf-system { prefix sys; }
  import yuma-ncx { prefix ncx; }

  organization "YumaWorks, Inc.";

  contact
    "Support <support@yumaworks.com>";

  description
    "YumaPro Deviations for IETF SYSTEM implementation

     Copyright (c) 2024, YumaWorks, Inc. All rights reserved.

     Redistribution and use in source and binary forms, with or
     without modification, is permitted pursuant to, and subject
     to the license terms contained in, the BSD 3-Clause License
     http://opensource.org/licenses/BSD-3-Clause";

  revision 2026-06-26 {
    description
      "25.10T-11: Remove the /system/radius deviation:
       the subtree is now used
       for RADIUS external group lookups.
       Mark the RADIUS shared-secret as a password.";
  }

  revision 2024-04-09 {
    description "Initial version.";
  }

  deviation "/sys:system/sys:contact" {
    description
      "The administrator contact information for the system
       is not supported yet.";
    deviate not-supported;
  }

  deviation "/sys:system/sys:location" {
    description
      "The system location is not supported yet.";
    deviate not-supported;
  }

  deviation "/sys:system/sys:ntp" {
    description
      "Configuration of the NTP client is not supported yet.";
    deviate not-supported;
  }

  deviation "/sys:system/sys:dns-resolver" {
    description
      "Configuration of the DNS resolver is not supported yet.";
    deviate not-supported;
  }

  deviation "/sys:system/sys:authentication" {
    description
      "The authentication configuration subtree is not supported yet.";
    deviate not-supported;
  }

  deviation "/sys:system/sys:radius/sys:server/sys:transport/" +
            "sys:udp/sys:udp/sys:shared-secret" {
    description
      "Mask the RADIUS shared secret in log output and in NETCONF replies,
       the same as the --radius-secret CLI parameter.";
    deviate add {
      ncx:password;
    }
  }
}
